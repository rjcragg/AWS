FME workspace InitialMachineCreator.fmw

Parameters:
- aws_connection = frank.zander Amazon Web Services   # "Amazon Web Services" AWS Web Connection

Note: The machine created will shut-down automatically when it is done installing everything. / That will take around 1 hour, but might be as fast as 30 minutes. / You should then log in to ensure that everything went according to plan, and then license FME.
PythonCaller_run_instances
    NEW_ATTRIBUTES = _response
    PYTHONSOURCE:
      import fme
      import fmeobjects
      import boto3    #need this for AWS access
      import json     #AWS stuff creates json


      def AWSCall(feature):
          ec2 = boto3.client(
                  'ec2',
                  region_name=feature.getAttribute('aws.region_name'),
                  aws_access_key_id=feature.getAttribute('AWS_ACCESS_KEY_ID'),
                  aws_secret_access_key=feature.getAttribute('AWS_SECRET_ACCESS_KEY'))
          try:
              response = ec2.run_instances(
                  BlockDeviceMappings=[
                      {
                          'DeviceName': '/dev/sda1',
                          'Ebs': {
                              'DeleteOnTermination': True,
                              'VolumeSize': feature.getAttribute('fme.volumeSize'),
                              'VolumeType': 'gp2',
                          },
                      },
                  ],
                  ImageId= feature.getAttribute('ImageId'),
                  InstanceType= feature.getAttribute('fme.ec2type') + '.' + feature.getAttribute('fme.ec2size'),
                  SecurityGroupIds=[
                      feature.getAttribute('GroupId'),
                  ],
                  SubnetId= feature.getAttribute('SubnetId'),
                  MinCount= 1, MaxCount= 1,
                  UserData=feature.getAttribute('UserData'),
                  TagSpecifications=[
                      {
                          'ResourceType': 'instance',
                          'Tags': [
                                          {'Key': 'Name', 'Value': feature.getAttribute('aws.name_tag') + ' AMI template'},
                                   ]
                       },
                   ],

              )
              feature.setAttribute("_response", json.dumps(response, default=str)) #https://stackoverflow.com/questions/11875770/how-to-overcome-datetime-datetime-not-json-serializable
          except Exception as e:
              feature.setAttribute("_exception", 'error in PythonCaller_run_instances: ' + repr(e))
    PYTHONSYMBOL = AWSCall
    -> PythonCaller_run_instances_Output
    -> AttributeExposer
PythonCaller_run_instances_Output: Logger
    LOG_FEATURE = LOG_ONLY
    MAXCOORDS = 20
    MAXFEATS = 20
    MESSAGE = Feature is:
    SEVERITY = WARN

Bookmark: Get parameters
Note: We need the aws access key and aws secret access key from the web connection for use in later PythonCallers.
PythonCreator_AWS_Credentials
    NEW_ATTRIBUTES = AWS_ACCESS_KEY_ID AWS_SECRET_ACCESS_KEY
    PYTHONSOURCE_NEW:
      import fme
      import fmeobjects
      import collections

      from fmewebservices import FMETokenConnection  # noqa
      from fmegeneral.webservices import NamedConnectionManager

      def aws_credentials_from_conn_name(feature):
         # noinspection PyArgumentList
         named_connection = NamedConnectionManager().getNamedConnection(
             FME_MacroValues['aws_connection']
         )  # type: FMETokenConnection

         try:
             key_vals = named_connection.getKeyValues()
             key = key_vals.get("AWS_ACCESS_KEY", None)
             secret = key_vals.get("AWS_SECRET", None)
             feature.setAttribute("AWS_ACCESS_KEY_ID", key)
             feature.setAttribute("AWS_SECRET_ACCESS_KEY", secret)
         except Exception as e:
             feature.setAttribute("_exception", 'PythonCreator_AWS_Credentials: ' + repr(e))
    PYTHONSYMBOL = aws_credentials_from_conn_name
    -> FeatureReader [INITIATOR]
Note: Get existing VpcId and region_name
FeatureReader
    ATTRIBUTES = JSONFeature,"git.username,git.repository,git.branch,aws.name_tag,aws.s3_bucket_name,aws.region_name,aws.vpc_cidr,aws.subnet_cidr{},ami.linux,ami.windows,flexnet.ec2type,flexnet.ec2size,flexnet.volumeSize,flexnet.securityGroup,fmeserver.ec2type,fmeserver.ec2size,fmeserver.volumeSize,fmeserver.securityGroup,fmeserver.docker-compose.yaml,fmeserver.vm.repository,fmeserver.vm.workspace,fmeserver.vm.server,fmeserver.vm.token,fme.ec2type,fme.ec2size,fme.volumeSize,fme.securityGroup,fme.timezone,fme.portForwarding,fme.firewall,fme.password,fme.license,fme.installApps,fme.vm.instanceInitiatedShutdownBehavior,fme.vm.fromEmail,fme.vm.CCEmail,fme.vm.BCCEmail,web.repository,web.workspace,web.server,web.token,git.aws.files{},fme.vm.template.email{},fme.vm.template.rdp{},fme_geometry{0}"
    ATTR_ACCUM_MODE = Merge Initiator and Result
    ATTR_CONFLICT_RES = Use Result
    COMBINE_GEOM = Use Initiator
    DATASET = ../settings.json
    FORMAT = JSON
    JSON_DECODE_TEXT_STRINGS = Yes
    JSON_FEATURE_TYPE_KEY = json_featuretype
    JSON_FLATTEN_MODE = ALL_LEVELS
    JSON_GEOMETRY_FORMAT = None
    JSON_SAVE_FRAGMENTS = NO
    JSON_SCAN_MODE = AUTO
    JSON_USE_BASENAME_AS_DEFAULT_FEATURE_TYPE = No
    JSON_USE_SEARCH_ENVELOPE = NO
    OUTPUT_FEATURES_DISPLAY = Schema and Data Features
    JSONFeature -> AttributeRemover
Note: clean up settings.json
AttributeRemover
    LIST_ATTRS = fme.vm.template.email{} fme.vm.template.rdp{} fme_geometry{}
    REMOVE_ATTRS = fmeserver.ec2type,fmeserver.ec2size,flexnet.volumeSize,fme.vm.CCEmail,fmeserver.vm.workspace,fmeserver.volumeSize,web.server,fmeserver.vm.repository,fme.vm.BCCEmail,flexnet.securityGroup,ami.linux,fme.vm.instanceInitiatedShutdownBehavior,web.token,fmeserver.vm.server,flexnet.ec2type,fme.vm.fromEmail,fmeserver.vm.token,fme.vm.template.rdp{0},fmeserver.securityGroup,flexnet.ec2size,fmeserver.docker-compose.yaml,web.workspace,fme.vm.template.email{0},web.repository
    -> AttributeCreator_UserData
Note: Populate UserData for when the instance is created
AttributeCreator_UserData
    ATTR_TABLE:
      SET_TO UserData = <script>

        :main
        	::::GENERAL SETTINGS FOR LATER IN BATCH FILE, and run procedures::::

        		set EC2PASSWORD=@Value(fme.password)
                setx /m EC2PASSWORD %EC2PASSWORD%
                set FMELICENSEIP=@Value(fme.license)
        		setx /m FMELICENSEIP %FMELICENSEIP%
                set RAWGIT=https://raw.githubusercontent.com/@Value(git.username)/@Value(git.repository)/@Value(git.branch)/
                setx /m RAWGIT %RAWGIT%
        		set TimeZone="@Value(fme.timezone)"
        		set OnstartConfigurationURL=https://raw.githubusercontent.com/@Value(git.username)/@Value(git.repository)/@Value(git.branch)/OnstartConfiguration.bat
        		set FMEDownloadInstall=https://raw.githubusercontent.com/@Value(git.username)/@Value(git.repository)/@Value(git.branch)/FMEInstalls/FMEDownloadInstall.bat
                set FMEUninstall=%RAWGIT%FMEInstalls/FMEUninstall.bat
        		set PORTFORWARDING=@Value(fme.portForwarding)
                set installApps=@Value(fme.installApps)
        		set Oracle64InstantClient=https://s3.amazonaws.com/FMETraining/instantclient-basiclite-windows.x64-12.1.0.2.0.zip
        		set NEWCOMPUTERNAME=FMETraining
        		set TEMP=c:\temp
        		set LOG=%TEMP%\InitialConfiguration.log

        	::Make required folders and get into it
        		md %TEMP%
        		pushd %TEMP%

        	:::::::::::::::::Here are the procedure calls:::::::::::::::::
        	:: Start Logging, and call sub routines for configuring the computer
        	::basicSetup sets things like license files. Always necessary
        		call :basicSetup > %LOG%
        	::ec2Setup sets things like computer password, timezone, etc.  Not necessary for non-ec2 training machines
        		call :ec2Setup >> %LOG%
        	::helpfulApps are applications that are helpful. Always necessary
        		call :helpfulApps >> %LOG%
        	::installFME installs FME Desktop and FME Server
        		call :installFME >> %LOG%
        	::oracle installs 32-bit and 64-bit Oracle Instant Clients
        		call :oracle >> %LOG%
        	::second run at Chocolatey; install all the other apps
        		call :choco >> %LOG%
        	::OnStartConfiguration.bat sets extra settings when new machine is made.
        		call :OnStartConfiguration >> %LOG%
        	::shut down the computer
        		call :shutdown >> %LOG%
        goto :eof

        :::::::::::::::::Everything below here are sub routines:::::::::::::::::
        :basicSetup
        		echo "Starting Downloading, Installing, and Configuring"
        	:: Log that variables are set correctly
        		echo "Variables are set to:"
        		set
        	::We should make sure port 80 is open too, for FME Server. This might be unnecessary
        		netsh firewall add portopening TCP 80 "FME Server"
        	::We should make sure port 25 is open too, for FME Server. Necessary for SMTP forwarding
        		netsh firewall add portopening TCP 25 "SMTP"
        	::We also need to open the port for UltraVNC. The installer fails to do that
        		netsh firewall add portopening TCP 5900 "VNC"
        		netsh firewall add portopening TCP 5800 "VNC"
        	::FME Server needs port 7078 opened for web sockets
        		netsh firewall add portopening TCP 7078 "WebSockets"
        	::Windows 2016 Server has stricter security settings that can block our RDP file from connecting. We can fix this with the following
        		reg add "HKLM\SYSTEM\CurrentControlSet\Control\Terminal Server\WinStations\RDP-Tcp" /v SecurityLayer /t REG_DWORD /d 0 /f
        goto :eof

        :ec2Setup
        	::::CONFIGURE WINDOWS SETTINGS::::
        	:: Set the time zone
        		tzutil /s %TimeZone%
        	:: The purpose of this section is to configure proxy ports for Remote Desktop
        	:: It must be run with elevated permissions (right-click and run as administrator)
        	:: The batch file assumes the computer name will not change.
        	:: Be sure to also open the listed ports in the EC2 security group
        	:: The ports to be set are in PORTFORWARDING:
        	:: First, we reset the existing proxy ports.
        		netsh interface portproxy reset
        	:: Now we set the proxy ports and add them to the firewall
        		for %%f IN (%PORTFORWARDING%) DO (
        			netsh interface portproxy add v4tov4 listenport=%%f connectport=3389 connectaddress=%NEWCOMPUTERNAME%
        			netsh firewall add portopening TCP %%f "Remote Desktop Port Proxy"
        		)
        	::Set Computer Name. This will require a reboot. Reboot is at the end of this batch file.
        		wmic computersystem where name="%COMPUTERNAME%" call rename name="%NEWCOMPUTERNAME%"
        	::Set Password for Administrator. I hate password complexity requiremens, but they can't be changed from the command line.
        		net user Administrator %EC2PASSWORD%
        	::Make sure password does not expire.
        		WMIC USERACCOUNT WHERE "Name='administrator'" SET PasswordExpires=FALSE
        goto :eof

        :OnStartConfiguration
        	::This section sets OnstartConfiguration.bat to run at ONSTART.
            schtasks /Create /F /RU SYSTEM /TN OnstartConfiguration /SC ONSTART /TR "cmd.exe /C aria2c.exe %OnstartConfigurationURL% --dir=/temp --allow-overwrite=true && c:\temp\OnstartConfiguration.bat"
        goto :eof

        :helpfulApps
        	::::INSTALL SOFTWARE::::
        	::Install Chocolatey  https://chocolatey.org/
        		@powershell -NoProfile -ExecutionPolicy Bypass -Command "iex ((new-object net.webclient).DownloadString('https://chocolatey.org/install.ps1'))" && SET PATH=%PATH%;%ALLUSERSPROFILE%\chocolatey\bin
        		::Some choco installs fail. Just get the absolute essentials now. The rest are added in the choco section
        		choco install aria2 7zip -y
        goto :eof

        :installFME
        	::Download the installer bat file and execute it. This requires the FMELICENSEIP and FMESERVERSERIAL environment variables
        	aria2c %FMEDownloadInstall% --out=FMEDownloadInstall.bat --allow-overwrite=true
            aria2c %FMEUninstall% --out=FMEUninstall.bat --allow-overwrite=true
        	CALL FMEDownloadInstall.bat
        goto :eof

        :oracle
        	::Install the 64 bit Oracle Instant Clients
        		aria2c %Oracle64InstantClient% --out=Oracle64InstantClient.zip --allow-overwrite=true
        		7z x -oc:\Oracle64InstantClient -aoa Oracle64InstantClient.zip
        		setx /m PATH "%PATH%;c:\Oracle64InstantClient\instantclient_12_1"
        goto :eof

        :choco
        	::Some additional packages to consider:
        		::github webdeploy carbon iisexpress
        	choco install %installApps% -y
        goto :eof

        :shutdown
        	::Shutdown the computer
        		echo Finished the Initial Configuration
        		echo Done! %date% %time%
        		shutdown /s /t 1
        goto :eof

        </script>
    -> PythonCaller_Describe_decribe_images

Bookmark: Find the most recent AMI for this region
PythonCaller_Describe_decribe_images
    NEW_ATTRIBUTES = _response
    PYTHONSOURCE:
      import fme
      import fmeobjects
      import boto3    #need this for AWS access
      import json     #AWS stuff creates json


      def AWSCall(feature):
          client = boto3.client(
                  'ec2',
                  region_name=feature.getAttribute('aws.region_name'),
                  aws_access_key_id=feature.getAttribute('AWS_ACCESS_KEY_ID'),
                  aws_secret_access_key=feature.getAttribute('AWS_SECRET_ACCESS_KEY'))
          try:
              response = client.describe_images(
                  ExecutableUsers=[
                      'all',
                  ],
                  Filters=[
                      {
                          'Name': 'state',
                          'Values': [
                              'available',
                          ]
                      },
                      {
                          'Name': 'platform',
                          'Values':  [
                              'windows',
                           ]
                      },
                      {
                          'Name': 'architecture',
                          'Values': [
                              'x86_64',
                          ]
                      },
                      {
                          'Name': 'image-type',
                          'Values': [
                              'machine',
                          ]
                      },
                      {
                          'Name': 'virtualization-type',
                          'Values': [
                              'hvm',
                          ]
                      },

                      {
                          'Name': 'block-device-mapping.volume-type',
                          'Values': [
                              'gp2',
                          ]
                      },
                      {
                          'Name': 'description',
                          'Values': [
                              feature.getAttribute('ami.windows'),
                          ]
                      },

                  ],


              )
              feature.setAttribute("_response", json.dumps(response, default=str)) #https://stackoverflow.com/questions/11875770/how-to-overcome-datetime-datetime-not-json-serializable
          except Exception as e:
              feature.setAttribute("_exception", 'error in PythonCaller_run_instances: ' + repr(e))
    PYTHONSYMBOL = AWSCall
    -> JSONFlattener_describe_images
    -> AttributeExposer
JSONFlattener_describe_images
    ERROR_LIST_ATTR = _json_error
    JSON_DOCUMENT = @Value(_response)
    NEW_ATTRIBUTES = Images{} Description ImageId CreationDate
    READ_FROM_FILE = NO
    RECURSIVE = Yes
    -> ListExploder_images
ListExploder_images
    ATTR_ACCUM_MODE = Merge List Attributes
    ATTR_CONFLICT_RES = Use List Attribute Values
    INDEX_ATTR = _element_index
    LIST_ATTR = Images{}
    ELEMENTS -> Sorter

Bookmark: Get the most recent by CreationDate
Sorter
    SORT_PARM = CreationDate ALPHA DESCENDING
    SORTED -> Sampler
Sampler
    RATE = 1
    SAMPLE_MODE = No
    SAMPLE_TYPE_LONG = First N Features
    SAMPLED -> PythonCaller_Describe_vpc

Bookmark: Find VPC
Note: Find VPC via Name tag
PythonCaller_Describe_vpc
    NEW_ATTRIBUTES = _response
    PYTHONSOURCE:
      import fme
      import fmeobjects
      import boto3    #need this for AWS access
      import json     #AWS stuff creates json


      def AWSCall(feature):
          client = boto3.client(
                  'ec2',
                  region_name=feature.getAttribute('aws.region_name'),
                  aws_access_key_id=feature.getAttribute('AWS_ACCESS_KEY_ID'),
                  aws_secret_access_key=feature.getAttribute('AWS_SECRET_ACCESS_KEY'))
          try:
              response = client.describe_vpcs(
                  Filters=[
                      {
                          'Name': 'tag:Name',
                          'Values': [
                              feature.getAttribute('aws.name_tag'),
                          ]
                      },
                  ],
              )
              feature.setAttribute("_response", json.dumps(response, default=str)) #https://stackoverflow.com/questions/11875770/how-to-overcome-datetime-datetime-not-json-serializable
          except Exception as e:
              feature.setAttribute("_exception", 'error in PythonCaller_run_instances: ' + repr(e))
    PYTHONSYMBOL = AWSCall
    -> JSONFlattener_vpcs
    -> AttributeExposer
JSONFlattener_vpcs
    ERROR_LIST_ATTR = _json_error
    JSON_DOCUMENT = @Value(_response)
    READ_FROM_FILE = NO
    RECURSIVE = Yes
    -> AttributeRenamer
AttributeRenamer
    ATTR_TABLE = RENAME_SET_DEFAULT Vpcs{0}.VpcId > VpcId
    -> PythonCaller_Describe_subnet

Bookmark: Find Subnet
Note: Get list of subnets
PythonCaller_Describe_subnet
    NEW_ATTRIBUTES = _response
    PYTHONSOURCE:
      import fme
      import fmeobjects
      import boto3    #need this for AWS access
      import json     #AWS stuff creates json


      def AWSCall(feature):
          client = boto3.client(
                  'ec2',
                  region_name=feature.getAttribute('aws.region_name'),
                  aws_access_key_id=feature.getAttribute('AWS_ACCESS_KEY_ID'),
                  aws_secret_access_key=feature.getAttribute('AWS_SECRET_ACCESS_KEY'))
          try:
              response = client.describe_subnets(
                  Filters=[
                      {
                          'Name': 'vpc-id',
                          'Values': [
                              feature.getAttribute('VpcId'),
                          ]
                      },
                  ],
              )
              feature.setAttribute("_response", json.dumps(response, default=str)) #https://stackoverflow.com/questions/11875770/how-to-overcome-datetime-datetime-not-json-serializable
          except Exception as e:
              feature.setAttribute("_exception", 'error in PythonCaller_run_instances: ' + repr(e))
    PYTHONSYMBOL = AWSCall
    -> JSONFlattener_subnet
    -> AttributeExposer
JSONFlattener_subnet
    ERROR_LIST_ATTR = _json_error
    JSON_DOCUMENT = @Value(_response)
    NEW_ATTRIBUTES = Subnets{} State SubnetId
    READ_FROM_FILE = NO
    RECURSIVE = Yes
    -> ListExploder
ListExploder
    ATTR_ACCUM_MODE = Merge List Attributes
    ATTR_CONFLICT_RES = Use List Attribute Values
    INDEX_ATTR = _element_index
    LIST_ATTR = Subnets{}
    ELEMENTS -> Tester_subnet_available
Note: Find an available subnet
Tester_subnet_available
    BOOL_OP = OR
    TEST_CLAUSE = TEST @Value(State) = available
    TEST_MODE = TEST
    PASSED -> Sampler_subnet
Note: We only need one
Sampler_subnet
    RATE = 1
    SAMPLE_MODE = No
    SAMPLE_TYPE_LONG = First N Features
    SAMPLED -> PythonCaller_Describe_security_groups

Bookmark: Find Security Group
Note: Find the security groups
PythonCaller_Describe_security_groups
    NEW_ATTRIBUTES = _response
    PYTHONSOURCE:
      import fme
      import fmeobjects
      import boto3    #need this for AWS access
      import json     #AWS stuff creates json


      def AWSCall(feature):
          client = boto3.client(
                  'ec2',
                  region_name=feature.getAttribute('aws.region_name'),
                  aws_access_key_id=feature.getAttribute('AWS_ACCESS_KEY_ID'),
                  aws_secret_access_key=feature.getAttribute('AWS_SECRET_ACCESS_KEY'))
          try:
              response = client.describe_security_groups(
                  Filters=[
                      {
                          'Name': 'vpc-id',
                          'Values': [
                              feature.getAttribute('VpcId'),
                          ]
                      },
                      {
                          'Name': 'group-name',
                          'Values': [
                              feature.getAttribute('fme.securityGroup'),
                          ]
                      },
                  ],

              )
              feature.setAttribute("_response", json.dumps(response, default=str)) #https://stackoverflow.com/questions/11875770/how-to-overcome-datetime-datetime-not-json-serializable
          except Exception as e:
              feature.setAttribute("_exception", 'error in PythonCaller_Describe_security_groups: ' + repr(e))
    PYTHONSYMBOL = AWSCall
    -> JSONFlattener_security
    -> AttributeExposer
JSONFlattener_security
    ERROR_LIST_ATTR = _json_error
    JSON_DOCUMENT = @Value(_response)
    NEW_ATTRIBUTES = SecurityGroups{} GroupId GroupName
    READ_FROM_FILE = NO
    RECURSIVE = Yes
    -> AttributeRenamer_GroupId
AttributeRenamer_GroupId
    ATTR_TABLE = RENAME_SET_DEFAULT SecurityGroups{0}.GroupId > GroupId
    -> PythonCaller_run_instances

Bookmark: Error in PythonCaller
AttributeExposer
    ATTR_LIST = _exception
    -> Tester_has_exception
Tester_has_exception
    BOOL_OP = OR
    TEST_CLAUSE = TEST _exception ATTRIBUTE_HAS_A_VALUE ""
    TEST_MODE = TEST
    PASSED -> Terminator_exception
Terminator_exception
    MESSAGE = Translation Terminated. @Value(_exception)
